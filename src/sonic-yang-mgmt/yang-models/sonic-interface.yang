module sonic-interface {

	namespace "http://github.com/Azure/sonic-interface";
	prefix intf;

	import ietf-yang-types {
		prefix yang;
	}

	import ietf-inet-types {
		prefix inet;
	}

	import sonic-head {
		prefix head;
		revision-date 2019-07-01;
	}

	import sonic-port {
		prefix port;
		revision-date 2019-07-01;
	}

	organization "Linkedin Corporation";

	contact "lnos_coders@linkedin.com";

	description "INTERFACE yang Module for SONiC OS";

	revision 2019-07-01 {
		description "First Revision";
	}

	container sonic-interface {

		container INTERFACE {

			description "INTERFACE part of config_db.json";

			list INTERFACE_LIST {

				description "INTERFACE part of config_db.json with vrf";

				key "port_name";

				leaf port_name {
					type leafref {
						path /port:sonic-port/port:PORT/port:PORT_LIST/port:port_name;
					}
				}

				leaf vrf_name {
					type string {
						pattern "Vrf[a-zA-Z0-9_-]+";
						length 3..255;
					}
				}
			}
			/* end of INTERFACE_LIST */

			list INTERFACE_IPPREFIX_LIST {

				description "INTERFACE part of config_db.json with ip-prefix";

				key "port_name ip-prefix";

				leaf port_name {
					/* This node must be present in INTERFACE_LIST */
					must "(current() = ../../INTERFACE_LIST[port_name=current()]/port_name)"
					{
						error-message "Must condition not satisfied, Try adding PORT: {}, Example: 'Ethernet0': {}";
					}

					type leafref {
						path /port:sonic-port/port:PORT/port:PORT_LIST/port:port_name;
					}
				}

				leaf ip-prefix {
					type union {
						type head:sonic-ip4-prefix;
						type head:sonic-ip6-prefix;
					}
				}

				leaf scope {
					type enumeration {
						enum global;
						enum local;
					}
				}

				leaf family {

					/* family leaf needed for backward compatibility
					   Both ip4 and ip6 address are string in IETF RFC 6021,
					   so must statement can check based on : or ., family
					   should be IPv4 or IPv6 according.
					 */

					must "(contains(../ip-prefix, ':') and current()='IPv6') or
						(contains(../ip-prefix, '.') and current()='IPv4')";
					type head:ip-family;
				}
			}
			/* end of INTERFACE_IPPREFIX_LIST */

		}
		/* end of INTERFACE container */
	}
}
